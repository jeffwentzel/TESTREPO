# JeffTest

# Specification: Software Requirement Specification

## DP-148: Introduction (Heading)

### DP-149: Purpose (Heading)

### DP-150: Scope (Heading)

### DP-151: References (Heading)

## DP-161: Component Design (Heading)

### DP-90: General design (Heading)

### DP-341: User Console (Heading)

#### DP-334 (Software Requirement)
The User Console will resemble a typical dashboard display and include options for system configuration.

#### DP-342: DrivePilot iPad Console Application (Heading)

##### DP-345 (Software Requirement)
iPad User Interface application can be downloadable through AppStore, but requires authentication code from DrivePilot to download and operate.

##### DP-351 (Software Requirement)
DrivePilot iPad console shall connect via secure Bluetooth to DrivePilot Controller.

###### DP-348 (Software Requirement)
The connection is established through the connect command of the Bluetooth v2.0 protocol.

#### DP-343: DrivePilot Android Console Application (Heading)

##### DP-347 (Software Requirement)
Android User Interface application can be downloadable through Google Play, but requires authentication code from DrivePilot to download and operate.

##### DP-353 (Software Requirement)
DrivePilot Android console shall connect via secure Bluetooth to DrivePilot Controller.

###### DP-349 (Software Requirement)
The connection is established through the connect command of the Bluetooth v2.0 protocol.

### DP-480: DrivePilot Command Controller for ARM and Motorola Chipset (Heading)

#### DP-346 (Software Requirement)
DrivePilot command controller is an ARM and Motorolla-processor based controlling computer with central interfaces to all DrivePilot capability.

#### DP-330 (Software Requirement)
The DCC shall conform to existing best practices for ARM processor circuit board design.
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
#### DP-331 (Software Requirement)
The DCC will operate on 4.3 Volts, 500mA with a variance tolerance of +/- 10%. Power outside of tolerances will trigger circuit protector fuses and switches and cause DrivePilot to shut down.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

### DP-481: Gear Relay Intercept (Heading)

#### DP-367 (Software Requirement)
Subprocessor, relay, and servo for intercepting both cable-based and electronic gear exchange:
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
### DP-484: Interfaces (Heading)

#### DP-358: Bluetooth module is connected to Part 2 of the motherboard. (Software Requirement)

### DP-485: Native User Console (Heading)

#### DP-355 (Software Requirement)
Native Console shall attach with wiring harness and mounts on vehicle dashboards.

### DP-482: Throttle Mechanism (Heading)

#### DP-438 (Software Requirement)
TAOS Design for in-dash mounting with conventional accelerator pedal applications.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

### DP-483: Steering Mechanism (Heading)

#### DP-439: SOS Design Interface SOS to Steering Gear assembly and Rotary value. (Software Requirement)

### DP-486: Braking Mechanism (Heading)

#### DP-440 (Software Requirement)
The BLC will include a universal mount method that is adapted into a variety of supported manufacturers' spaces.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

## DP-169: Requirements Traceability (Heading)
